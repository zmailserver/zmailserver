ZIMBRA-TRAP-MIB DEFINITIONS ::= BEGIN
        IMPORTS zmail FROM ZIMBRA-MIB;

zmtraps OBJECT IDENTIFIER ::= { zmail 0 }

zmServiceStatusTrap NOTIFICATION-TYPE
        STATUS current
        DESCRIPTION "Service Status Change"
        ::= { zmtraps 0 }

END
